module sonic-bgp-neighbor {
    namespace "http://github.com/Azure/sonic-bgp-neighbor";
    prefix bgpnbr;
    yang-version 1.1;
    import ietf-inet-types {
        prefix inet;
    }
    organization
        "SONiC";
    contact
        "SONiC";
    description
        "SONIC BGP Neighbor";
    revision 2021-02-26 {
        description
            "Initial revision.";
    }
    container sonic-bgp-neighbor {
        container BGP_NEIGHBOR {
            list BGP_NEIGHBOR_TEMPLATE_LIST {
                description "This list is to support template based BGP neighbor configuration handled by bgpcfgd";
                key "neighbor";
                leaf neighbor {
                    type inet:ip-address;
                    description "BGP Neighbor address";
                }
                leaf rrclient {
                    type uint8 {
                        range "0..1";
                   }
                    description "Route reflector client";
                }
                leaf local_addr {
                    type inet:ip-address;
                    description "Local source address or interface name to use for connection.";
                }
                leaf nhopself {
                    type uint8 {
                        range "0..1";
                    }
                    description "Nexthop is self, no nexthop calculation";
                }
                leaf holdtime {
                    type uint16;
                    description "Hold time";
                }
                leaf asn {
                    type uint32 {
                        range "1..4294967295";
                    }
                    description "Peer AS number";
                }
                leaf keepalive {
                    type uint16;
                    description "Keepalive interval";
                }
            }
        }
    }
}
